# Specification: Specification Document
- Description: Requirements Document

## REQ-0010 (Requirement Type)
The system shall monitor equipments each 5 ms and report failures to the Flight Warning System
- Derived: false
- status: TBC

## REQ-0020 (Requirement Type)
All failures must be stored for two months
- Derived: false
- status: Draft

## REQ-0030 (Requirement Type)
A failure is confirmed if there have been 2 successive frames for same equipement
- status: TBC
- Derived: false
- applicability: V2

## REQ-0040 (Requirement Type)
Frame acquisition must use AFDX or ARINC protocols according to equipments monitored
- Derived: true
- status: TBC
- revision: 2

## REQ-0050 (Requirement Type)
List of equipments to monitor shall be managed in a configuration file loaded at startup
- Derived: false
- status: FINALIZED

## R2

## R7 (Requirement Type)
REQ-1

## R8 (Requirement Type)
REQ-1
